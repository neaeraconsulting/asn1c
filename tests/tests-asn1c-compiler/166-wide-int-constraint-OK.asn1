-- OK: Everything is fine

-- iso.org.dod.internet.private.enterprise (1.3.6.1.4.1)
-- .spelio.software.asn1c.test (9363.1.5.1)
-- .166

ModuleWideIntConstraint
	{ iso org(3) dod(6) internet(1) private(4) enterprise(1)
		spelio(9363) software(1) asn1c(5) test(1) 166 }
	DEFINITIONS AUTOMATIC TAGS ::=
BEGIN

	-- With -fwide-types the constraints must not depend on the
	-- size of long, which is 32 bits on some 64-bit platforms.
	Uint64 ::= INTEGER (0..18446744073709551615)
	Time64 ::= Uint64
	Signed40 ::= INTEGER (-549755813888..549755813887)
	Small ::= INTEGER (0..255)

END
